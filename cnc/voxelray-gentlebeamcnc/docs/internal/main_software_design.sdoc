[DOCUMENT]
TITLE: Heracles Software Design Document for Internal GUI
UID: DHF-HRC-0033
METADATA:
  COMPONENT: heracles-internal-gui

[GRAMMAR]
IMPORT_FROM_FILE: @grammar

[[SECTION]]
TITLE: Purpose

[TEXT]
STATEMENT: >>>
The purpose of this document is to outline the design specifications of the Heracles Internal GUI Software.
<<<

[[/SECTION]]

[[SECTION]]
TITLE: Scope

[TEXT]
STATEMENT: >>>
This document describes the design modules and sub-modules of the Heracles Internal GUI Software.

The information in this document is derived from the Internal GUI SRS, referenced in this document.

\*The term Software applies to both Software and Firmware components.
<<<

[[/SECTION]]

[[SECTION]]
TITLE: Abbreviations and Definitions

[TEXT]
STATEMENT: >>>
FW
Firmware

MCU
Microcontroller Unit

PRS
Product Requirements Specification

SDP
Software Development Plan

SRS
Software Requirements Specification

SVP
Software Verification Plan

SW
Software
<<<

[[/SECTION]]

[[SECTION]]
TITLE: Overview

[TEXT]
STATEMENT: >>>
The Internal GUI SW provides a means for the user to maintain demographic patient data, including treatment plans. It communicates with the record and verify component and flange camera stream.

The internal GUI software runs on an industrial PC located at the base of the system
<<<

[[/SECTION]]

[[SECTION]]
TITLE: References

[TEXT]
STATEMENT: >>>
Document ID / Reference Number: DHF-HRC-0001, Rev. 2
Document Title: Heracles Software Development Plan (SDP)

Document ID / Reference Number: DHF-HRC-0003, Rev. 2
Document Title: Heracles Software Verification Plan (SVP)

Document ID / Reference Number: DHF-HRC-0005, Rev. 3
Document Title: Heracles Internal GUI Software Requirements Specification (SRS)

Document ID / Reference Number: DHF-HRC-0004, Rev. 2
Document Title: Heracles Software Architecture Description
<<<

[[/SECTION]]

[[SECTION]]
TITLE: Architecture Overview

[TEXT]
STATEMENT: >>>
High Level System Architecture

Main Modules

The design of the application is based on the MVVM pattern. There are three core components in the MVVM pattern: the model, the view, and the view model. Each serves a distinct purpose. The diagram below shows the relationships between the three components.

The MVVN design pattern is implemented in the application as follows: the 4 th layer is the gRPC wrapper for communication with Record and Verify services.
<<<

[[/SECTION]]

[[SECTION]]
PREFIX: SW-H10SG-
TITLE: Design Items

[DESIGN_ITEM]
UID: SW-H10SG-11
TITLE: Data management API
STATEMENT: >>>
The application shall use a streaming communication (API) to store and retrieve data remotely from/to the centralized data storage (Database) to allow seamless and sustainable integration.

The list of API functions is defined in the following protocol document:

Heracles DB API
<<<

[DESIGN_ITEM]
UID: SW-H10SG-12
TITLE: Patients' Data Management
STATEMENT: >>>
The application shall include a centralized and secure data repository for storing and managing all treatment planning data, including patient information, treatment plans, and treatment history.

Patient Table will be stored in a secure manner, and data will be encrypted.

The data shall be managed in a relational database, which shall support hierarchical organization based on user flow.

The data shall be stored in the form of JSON-serialized Protocol Buffers based on the communication protocol. 
Each Protocol Buffers structure shall have a dedicated database table with the following fields:

- ID
- Parent ID
- Data (serialized JSON)

<<<
RELATIONS:
- TYPE: Parent
  VALUE: RQ-H10SG-55
  ROLE: Refines

[DESIGN_ITEM]
UID: SW-H10SG-13
TITLE: High Level System Architecture
STATEMENT: >>>
Approvals Calibration - Heater current configuration.

The application is comprised of two key components: Heracles Device Control console (Indoor application) and Treatment Control console (Outdoor application).

The Heracles Device Control console is integrated within the Heracles device. This application addresses functionalities related to patients, demographic data management, clinical data management, treatment data management, user access, clinical workflows, and system setup and services.

The Treatment Control application must be located in a console outside the treatment room. This is to provide the operator with a safe work environment. It should allow healthcare professionals e.g., radiation therapists (RTT), and physicians to activate the radiation emission for the patient's treatment and to provide tools for physicists to program the system's calibration values.
<<<

[DESIGN_ITEM]
UID: SW-H10SG-99
TITLE: Collimator fields name mapping to DB, UI and GCB
STATEMENT: >>>
61 Head collimator Patients - Plan View - Load For Treatment - Cancelation

+------------------------+-----------------+
| Enum Name              | FW: GCB /UI     |
+========================+=================+
| FIELD_NAME_UNSPECIFIED | N/A             |
+------------------------+-----------------+
| FIELD_NAME_PLUS_4L2    | FW: +4L2 UI: 1  |
+------------------------+-----------------+
| FIELD_NAME_PLUS_4L1    | FW: +4L1 UI: 2  |
+------------------------+-----------------+
| FIELD_NAME_PLUS_4C     | FW: +4C UI: 3   |
+------------------------+-----------------+
| FIELD_NAME_PLUS_4R1    | FW: +4R1 UI: 4  |
+------------------------+-----------------+
| FIELD_NAME_PLUS_4R2    | FW: +4R2 UI: 5  |
+------------------------+-----------------+
| FIELD_NAME_PLUS_3L3    | FW: +3L3 UI: 6  |
+------------------------+-----------------+
| FIELD_NAME_PLUS_3L2    | FW: +3L2 UI: 7  |
+------------------------+-----------------+
| FIELD_NAME_PLUS_3L1    | FW: +3L1 UI: 8  |
+------------------------+-----------------+
| FIELD_NAME_PLUS_3R1    | FW: +3R1 UI: 9  |
+------------------------+-----------------+
| FIELD_NAME_PLUS_3R2    | FW: +3R2 UI: 10 |
+------------------------+-----------------+
| FIELD_NAME_PLUS_3R3    | FW: +3R3 UI: 11 |
+------------------------+-----------------+
| FIELD_NAME_PLUS_2L3    | FW: +2L3 UI: 12 |
+------------------------+-----------------+
| FIELD_NAME_PLUS_2L2    | FW: +2L2 UI: 13 |
+------------------------+-----------------+

+----------------------+-----------------+
| FIELD_NAME_PLUS_2L1  | FW: +2L1 UI: 14 |
+======================+=================+
| FIELD_NAME_PLUS_2C   | FW: +2C UI: 15  |
+----------------------+-----------------+
| FIELD_NAME_PLUS_2R1  | FW: +2R1 UI: 16 |
+----------------------+-----------------+
| FIELD_NAME_PLUS_2R2  | FW: +2R2 UI: 17 |
+----------------------+-----------------+
| FIELD_NAME_PLUS_2R3  | FW: +2R3 UI: 18 |
+----------------------+-----------------+
| FIELD_NAME_PLUS_1L4  | FW: +1L4 UI: 19 |
+----------------------+-----------------+
| FIELD_NAME_PLUS_1L3  | FW: +1L3 UI: 20 |
+----------------------+-----------------+
| FIELD_NAME_PLUS_1L2  | FW: +1L2 UI: 21 |
+----------------------+-----------------+
| FIELD_NAME_PLUS_1L1  | FW: +1L1 UI: 22 |
+----------------------+-----------------+
| FIELD_NAME_PLUS_1R1  | FW: +1R1 UI: 23 |
+----------------------+-----------------+
| FIELD_NAME_PLUS_1R2  | FW: +1R2 UI: 24 |
+----------------------+-----------------+
| FIELD_NAME_PLUS_1R3  | FW: +1R3 UI: 25 |
+----------------------+-----------------+
| FIELD_NAME_PLUS_1R4  | FW: +1R4 UI: 26 |
+----------------------+-----------------+
| FIELD_NAME_PLUS_0L4  | FW: +0L4 UI: 27 |
+----------------------+-----------------+
| FIELD_NAME_PLUS_0L3  | FW: +0L3 UI: 28 |
+----------------------+-----------------+
| FIELD_NAME_PLUS_0L2  | FW: +0L2 UI: 29 |
+----------------------+-----------------+
| FIELD_NAME_PLUS_0L1  | FW: +0L1 UI: 30 |
+----------------------+-----------------+
| FIELD_NAME_PLUS_C    | FW: C UI: 31    |
+----------------------+-----------------+
| FIELD_NAME_PLUS_0R1  | FW: +0R1 UI: 32 |
+----------------------+-----------------+
| FIELD_NAME_PLUS_0R2  | FW: +0R2 UI: 33 |
+----------------------+-----------------+
| FIELD_NAME_PLUS_0R3  | FW: +0R3 UI: 34 |
+----------------------+-----------------+
| FIELD_NAME_PLUS_0R4  | FW: +0R4 UI: 35 |
+----------------------+-----------------+
| FIELD_NAME_MINUS_1L4 | FW: -1L4 UI: 36 |
+----------------------+-----------------+

+----------------------+-----------------+
| FIELD_NAME_MINUS_1L3 | FW: -1L3 UI: 37 |
+======================+=================+
| FIELD_NAME_MINUS_1L2 | FW: -1L2 UI: 38 |
+----------------------+-----------------+
| FIELD_NAME_MINUS_1L1 | FW: -1L1 UI: 39 |
+----------------------+-----------------+
| FIELD_NAME_MINUS_1R1 | FW: -1R1 UI: 40 |
+----------------------+-----------------+
| FIELD_NAME_MINUS_1R2 | FW: -1R2 UI: 41 |
+----------------------+-----------------+
| FIELD_NAME_MINUS_1R3 | FW: -1R3 UI: 42 |
+----------------------+-----------------+
| FIELD_NAME_MINUS_1R4 | FW: -1R4 UI: 43 |
+----------------------+-----------------+
| FIELD_NAME_MINUS_2L3 | FW: -2L3 UI: 44 |
+----------------------+-----------------+
| FIELD_NAME_MINUS_2L2 | FW: -2L2 UI: 45 |
+----------------------+-----------------+
| FIELD_NAME_MINUS_2L1 | FW: -2L1 UI: 46 |
+----------------------+-----------------+
| FIELD_NAME_MINUS_2C  | FW: -2C UI: 47  |
+----------------------+-----------------+
| FIELD_NAME_MINUS_2R1 | FW: -2R1 UI: 48 |
+----------------------+-----------------+
| FIELD_NAME_MINUS_2R2 | FW: -2R2 UI: 49 |
+----------------------+-----------------+
| FIELD_NAME_MINUS_2R3 | FW: -2R3 UI: 50 |
+----------------------+-----------------+
| FIELD_NAME_MINUS_3L3 | FW: -3L3 UI: 51 |
+----------------------+-----------------+
| FIELD_NAME_MINUS_3L2 | FW: -3L2 UI: 52 |
+----------------------+-----------------+
| FIELD_NAME_MINUS_3L1 | FW: -3L1 UI: 53 |
+----------------------+-----------------+
| FIELD_NAME_MINUS_3R1 | FW: -3R1 UI: 54 |
+----------------------+-----------------+
| FIELD_NAME_MINUS_3R2 | FW: -3R2 UI: 55 |
+----------------------+-----------------+
| FIELD_NAME_MINUS_3R3 | FW: -3R3 UI: 56 |
+----------------------+-----------------+
| FIELD_NAME_MINUS_4L2 | FW: -4L2 UI: 57 |
+----------------------+-----------------+
| FIELD_NAME_MINUS_4L1 | FW: -4L1 UI: 58 |
+----------------------+-----------------+
| FIELD_NAME_MINUS_4C  | FW: -4C UI: 59  |
+----------------------+-----------------+

+----------------------+-----------------+
| FIELD_NAME_MINUS_4R1 | FW: -4R1 UI: 60 |
+======================+=================+
| FIELD_NAME_MINUS_4R2 | FW: -4R2 UI: 61 |
+----------------------+-----------------+

13 Cells Central Large collimator

+------------------------+-----------------+
| Enum Name              | FW: GCB /UI     |
+========================+=================+
| FIELD_NAME_UNSPECIFIED | N/A             |
+------------------------+-----------------+
| FIELD_NAME_PLUS_2L1    | FW: +2L1 UI: 1  |
+------------------------+-----------------+
| FIELD_NAME_PLUS_2C     | FW: +2C UI: 2   |
+------------------------+-----------------+
| FIELD_NAME_PLUS_2R1    | FW: +2R1 UI: 3  |
+------------------------+-----------------+
| FIELD_NAME_PLUS_1L2    | FW: +1L2 UI: 4  |
+------------------------+-----------------+
| FIELD_NAME_PLUS_1R2    | FW: +1R2 UI: 5  |
+------------------------+-----------------+
| FIELD_NAME_PLUS_0L2    | FW: +0L2 UI: 6  |
+------------------------+-----------------+
| FIELD_NAME_PLUS_C      | FW: C UI: 7     |
+------------------------+-----------------+
| FIELD_NAME_PLUS_0R2    | FW: +0R2 UI: 8  |
+------------------------+-----------------+
| FIELD_NAME_MINUS_1L2   | FW: -1L2 UI: 9  |
+------------------------+-----------------+
| FIELD_NAME_MINUS_1R2   | FW: -1R2 UI: 10 |
+------------------------+-----------------+
| FIELD_NAME_MINUS_2L1   | FW: -2L1 UI: 11 |
+------------------------+-----------------+
| FIELD_NAME_MINUS_2C    | FW: -2C UI: 12  |
+------------------------+-----------------+
| FIELD_NAME_MINUS_2R1   | FW: -2R1 UI: 13 |
+------------------------+-----------------+
<<<
RELATIONS:
- TYPE: Parent
  VALUE: RQ-H10SG-81
  ROLE: Refines

[DESIGN_ITEM]
UID: SW-H10SG-100
TITLE: System Data management
STATEMENT: >>>
The application shall include a centralized and secure data repository for storing device system data, including calibration data, system settings, QC history, and warmup history.

The data shall be managed in a relational database.

<<<

[DESIGN_ITEM]
UID: SW-H10SG-333
TITLE: Automatically Identify connected collimator type and configuration
STATEMENT: >>>
The Identification of the connected Collimator will be done according to the following sequence diagram:

1. The C&C app queries the connected collimator (chip) for its ID (64-bit ID).

1. The C&C queries DB Service (Moses) for the collimator data for this ID. The return value includes a foreign key for the collimator\_configuration.

2. The C&C queries DB Service for the collimator's configuration, which returns the Type, Energy, and SSD of the connected collimator.
<<<
RELATIONS:
- TYPE: Parent
  VALUE: RQ-H10SG-332
  ROLE: Refines

[DESIGN_ITEM]
UID: SW-H10SG-378
TITLE: Patient - Plan View - Auto-calculate the ICDCode - ICD Code table
STATEMENT: >>>
ICD Code will be generated based on the lesion location (Field Location) and the Pathology as set by the operator:

The calculation will use the following table:

+------------------------------------------------------------------------------+-----------+--------------------------------------------------------+----------------------------------------+-----------------------------+---------------------+
|                                                                              | ICDforBCC | ICDforSCC                                              | ICDforSCC-15                           | ICDforBasosquam             | ICD for Keloid      |
+==============================================================================+===========+========================================================+========================================+=============================+=====================+
| Location                                                                     |           | Basal Cell Carcinoma (Bcc)Squamous Cell Carcinoma(ScC) | Squamous CellCarcinoma-in Situ(SCC-IS) | Basosquamous Cell Carcinoma | Keloid L91.0, L73.0 |
+------------------------------------------------------------------------------+-----------+--------------------------------------------------------+----------------------------------------+-----------------------------+---------------------+
| Breast                                                                       | C44.511   | C44.521                                                | D04.5                                  | C44.591                     |                     |
+------------------------------------------------------------------------------+-----------+--------------------------------------------------------+----------------------------------------+-----------------------------+---------------------+
| Ear (Left)                                                                   | C44.219   | C44.229                                                | D04.22                                 | C44.299                     |                     |
+------------------------------------------------------------------------------+-----------+--------------------------------------------------------+----------------------------------------+-----------------------------+---------------------+
| Ear (Right)                                                                  | C44.212   | C44.222                                                | D04.21                                 | C44.292                     |                     |
+------------------------------------------------------------------------------+-----------+--------------------------------------------------------+----------------------------------------+-----------------------------+---------------------+
| Face&Other Parts of Face [Ex. Cheek,Chin, Forehead,Jaw,Pre-Auricular,Zygoma) | C44.319   | C44.329                                                | D04.39                                 | C44.399                     |                     |
+------------------------------------------------------------------------------+-----------+--------------------------------------------------------+----------------------------------------+-----------------------------+---------------------+
| Lip                                                                          | C44.01    | C44.02                                                 | D04.0                                  | C44.09                      |                     |
+------------------------------------------------------------------------------+-----------+--------------------------------------------------------+----------------------------------------+-----------------------------+---------------------+
| Neck                                                                         | C44.41    | C44.42                                                 | D04.4                                  | C44.49                      |                     |
+------------------------------------------------------------------------------+-----------+--------------------------------------------------------+----------------------------------------+-----------------------------+---------------------+
| Nose (Ex. Ala, Bridge, Tip, Root)                                            | C44.311   | C44.321                                                | D04.39                                 | C44.391                     |                     |
+------------------------------------------------------------------------------+-----------+--------------------------------------------------------+----------------------------------------+-----------------------------+---------------------+
| Scalp &Post Auricular                                                        | C44.41    | C44.42                                                 | D04.4                                  | C44.49                      |                     |
+------------------------------------------------------------------------------+-----------+--------------------------------------------------------+----------------------------------------+-----------------------------+---------------------+
| Trunk/Chest/Abdomen/Back                                                     | C44.519   | C44.529                                                | D04.5                                  | C44.599                     |                     |
+------------------------------------------------------------------------------+-----------+--------------------------------------------------------+----------------------------------------+-----------------------------+---------------------+
| Lower Limb (Left) (Including Hip)                                            | C44.719   | C44.729                                                | D04.72                                 | C44.799                     |                     |
+------------------------------------------------------------------------------+-----------+--------------------------------------------------------+----------------------------------------+-----------------------------+---------------------+
| Lower Limb (Right) (Including Hip)                                           | C44.712   | C44.722                                                | D04.71                                 | C44.792                     |                     |
+------------------------------------------------------------------------------+-----------+--------------------------------------------------------+----------------------------------------+-----------------------------+---------------------+
| Upper Limb (Left) (including Shoulder)                                       | C44.619   | C44.629                                                | D04.62                                 | C44.699                     |                     |
+------------------------------------------------------------------------------+-----------+--------------------------------------------------------+----------------------------------------+-----------------------------+---------------------+
| Upper Limb (Right) (including Shoulder)                                      | C44.612   | C44.622                                                | D04.61                                 | C44.692                     |                     |
+------------------------------------------------------------------------------+-----------+--------------------------------------------------------+----------------------------------------+-----------------------------+---------------------+
| Eyelids:                                                                     | C44.1121  | C44.1221                                               | D04.111                                | C44.1992                    |                     |
+------------------------------------------------------------------------------+-----------+--------------------------------------------------------+----------------------------------------+-----------------------------+---------------------+
| Eyelid (Right Upper) Eyelid (Right Lower)including Canthus                   | C44.1122  | C44.1222                                               | D04.112                                | C44.1991                    |                     |
+------------------------------------------------------------------------------+-----------+--------------------------------------------------------+----------------------------------------+-----------------------------+---------------------+
| Eyelid (Left Upper)                                                          | C44.1191  | C44.1291                                               | D04.121                                | C44.1922                    |                     |
+------------------------------------------------------------------------------+-----------+--------------------------------------------------------+----------------------------------------+-----------------------------+---------------------+
| Eyelid (Left Lower) including Canthus                                        | C44.1192  | C44.1292                                               | D04.122                                | C44.1921                    |                     |
+------------------------------------------------------------------------------+-----------+--------------------------------------------------------+----------------------------------------+-----------------------------+---------------------+
| Unspecified Parts of Face (Find More Specific Fit)                           | C44.310   | C44.320                                                | D04.30                                 |                             |                     |
+------------------------------------------------------------------------------+-----------+--------------------------------------------------------+----------------------------------------+-----------------------------+---------------------+
| Unspecified Codes (Find More Specific Fit)                                   | C44.91    | C44.92                                                 | D04.9                                  |                             |                     |
+------------------------------------------------------------------------------+-----------+--------------------------------------------------------+----------------------------------------+-----------------------------+---------------------+
| Unspecified Eyelid (Find More Specific Fit)                                  | C44.111   | C44.121                                                | D04.10                                 |                             |                     |
+------------------------------------------------------------------------------+-----------+--------------------------------------------------------+----------------------------------------+-----------------------------+---------------------+
<<<
RELATIONS:
- TYPE: Parent
  VALUE: RQ-H10SG-345
  ROLE: Refines

[DESIGN_ITEM]
UID: SW-H10SG-622
TITLE: User Login Sequence
STATEMENT: >>>
1. The user is presented with username and password.
2. The credentials are validated by the UsersService.
3. If authentication fails, the error is presented to the user.
4. Otherwise, the application AuthorizedUser is configured with the issued auth token and user information and the login screen closes to the main application screen.
<<<
RELATIONS:
- TYPE: Parent
  VALUE: RQ-H10SG-74
  ROLE: Refines

[DESIGN_ITEM]
UID: SW-H10SG-623
TITLE: Disable Treatment when the Patient's Plan is Inconsistent
STATEMENT: >>>
Sequence Diagram:
Sequence Diagram:

.. raw:: html

   <pre class="mermaid">
   sequenceDiagram
       autonumber
       participant PrescriptionModel
       participant PlanViewModel
       participant CollimatorModel
       participant PlanModel

       PrescriptionModel->>PlanViewModel: Prescription changed
       activate PlanViewModel
       PlanViewModel->>PlanModel: fetch latest plan
       activate PlanModel
       
       Note over PlanModel: fetch plan data
       PlanModel-->>PlanViewModel: plan
       deactivate PlanModel
       
       PlanViewModel->>CollimatorModel: get active collimator
       CollimatorModel-->>PlanViewModel: 
       
       Note over PlanViewModel: check collimator

       alt collimator mismatch
           Note over PlanViewModel: disable treatment
           Note over PlanViewModel: show message
       end
       deactivate PlanViewModel
   </pre>
<<<
RELATIONS:
- TYPE: Parent
  VALUE: RQ-H10SG-14
  ROLE: Refines
- TYPE: Parent
  VALUE: RQ-H10SG-15
  ROLE: Refines

[DESIGN_ITEM]
UID: SW-H10SG-624
TITLE: Patient's treatment fields Audit Trial
STATEMENT: >>>
Sequence Diagram for saving audit for Plan and Treatment Fields creation
<<<
RELATIONS:
- TYPE: Parent
  VALUE: RQ-H10SG-16
  ROLE: Refines

[DESIGN_ITEM]
UID: SW-H10SG-625
TITLE: Approve Patient's Treatment Fields (Plan)
STATEMENT: >>>
Sequence diagram for 'approve plan' use case:

.. raw:: html

   <pre class="mermaid">
   sequenceDiagram
    actor User
    
    box rgb(245, 245, 245) Application
        participant PlanViewModel
        participant PlanModel
    end
    
    box rgb(245, 245, 245) Server
        participant Storage
    end

    User->>PlanViewModel: change plan status
    PlanViewModel->>User: show dialog
    User->>PlanViewModel: credentials & desired status
    
    PlanViewModel->>Storage: authenticate user
    activate Storage
    Storage->>Storage: handle request
    Storage-->>PlanViewModel: response
    deactivate Storage
    
    alt successful authentication
        PlanViewModel->>PlanModel: change plan status
        
        PlanModel->>Storage: save changes
        activate Storage
        Storage->>Storage: save plan
        Storage-->>PlanModel: saved plan
        deactivate Storage
    end
   </pre>
<<<
RELATIONS:
- TYPE: Parent
  VALUE: RQ-H10SG-17
  ROLE: Refines

[DESIGN_ITEM]
UID: SW-H10SG-626
TITLE: Refresh Patient's Treatment Fields from the database
STATEMENT: >>>

.. raw:: html

   <pre class="mermaid">
   sequenceDiagram
       autonumber
       actor User

       box Application
           participant PlanViewModel
           participant PlanModel
       end

       box Server
           participant Storage
       end

       User->>PlanViewModel: refresh treatment fields
       activate PlanViewModel
       PlanViewModel->>PlanModel: fetch fields
       activate PlanModel
       
       Note over PlanModel: clear displayed fields
       PlanModel->>Storage: query stored fields
       activate Storage
       Note over Storage: handle request
       Storage-->>PlanModel: treatment fields
       deactivate Storage
       
       Note over PlanModel: update displayed fields
       PlanModel-->>PlanViewModel: 
       PlanViewModel-->>User: display fields

       PlanViewModel->>PlanModel: validate field doses
       Note over PlanModel: verify dose calculations
       PlanModel-->>PlanViewModel: validity status
       deactivate PlanModel

       alt validation fails
           Note over PlanViewModel: disable treatment
           PlanViewModel-->>User: show warning
       end
       deactivate PlanViewModel
   </pre>

Fulfilled requirements:
- RQ-H10SG-18-#9: Patients - Plan view - Refresh Patient's Treatment Fields from the database
- RQ-H10SG-21-#11: Patients - Plan view - View Patient's Plan's Treatment Fields
<<<

[DESIGN_ITEM]
UID: SW-H10SG-628
TITLE: Update Patient's Treatment Fields for a Plan
STATEMENT: >>>
Update patient's treatment fields:
1. If the plan is not approved, a read-only plan is displayed.
2. Otherwise, emission duration input is enabled.
3. User selects fields.
4. If a single field is selected, the delete button is enabled.
5. Otherwise, the add button or update and delete buttons are enabled depending on if it is an existing plan field.
<<<
RELATIONS:
- TYPE: Parent
  VALUE: RQ-H10SG-192
  ROLE: Refines

[DESIGN_ITEM]
UID: SW-H10SG-629
TITLE: Search Filtering
STATEMENT: >>>
The application shall provide search and filtering capabilities in the system logs view to allow operators to find and view specific log entries. The search and filtering functionality shall enable filtering by various criteria to help locate relevant system events.

The sequence diagram for the search filtering process is provided in the attached diagram.

.. raw:: html

   <pre class="mermaid">
   sequenceDiagram
       autonumber
       actor User

       box Application
           participant LogViewModel
           participant CreateFilterDialog
       end

       alt adding a filter
           User->>LogViewModel: add filter
           activate LogViewModel
           LogViewModel->>CreateFilterDialog: show dialog
           activate CreateFilterDialog
           CreateFilterDialog-->>User: select field to filter
           User->>CreateFilterDialog: selected field
           CreateFilterDialog-->>User: select message type
           User->>CreateFilterDialog: selected type
           CreateFilterDialog-->>LogViewModel: 
           deactivate CreateFilterDialog
           
           Note over LogViewModel: add new filter
           LogViewModel-->>User: updated list of records
           deactivate LogViewModel
       end

       alt removing a filter
           User->>LogViewModel: remove chosen filter
           activate LogViewModel
           Note over LogViewModel: remove the filter
           LogViewModel-->>User: updated list of records
           deactivate LogViewModel
       end
   </pre>

Fulfilled requirements:
- RQ-H10SG-22-#9: System Logs' View - Search Filtering

Attachments:
- H10SG-22.sequence.mermaid.drawio.png (121.61 kB)
<<<

[DESIGN_ITEM]
UID: SW-H10SG-630
TITLE: Editing Patient's Prescription
STATEMENT: >>>
The application shall allow operators to edit and modify a patient's prescription within the treatment planning interface. The prescription editing functionality enables updates to prescription parameters and details associated with a patient's treatment plan.

The operator shall be able to modify prescription details and have these changes reflected in the patient's treatment plan.

.. raw:: html

    <pre class="mermaid">
    graph TD
        A[Prescription update] --> B{Simulation exists?}
        B -- No --> C[Empty form, disable all buttons]
        B -- Yes --> D[Enable Add button]
        D --> E{Prescription exists?}
        E -- Yes --> F[Fill the form]
        E -- No --> G[User clicks Add]
        G --> H[Create blank prescription]
        H --> F
        F --> I{Prescription is approved?}
        I -- Yes --> J[Readonly form]
        I -- No --> K[Enable form inputs]
        K --> L[User edits the form]
        L --> M[Enable Save and Refresh buttons]
    </pre>

Fulfilled requirements:
- RQ-H10SG-23-#9: Patients - Plan View - Edit Patient's Prescription
<<<
RELATIONS:
- TYPE: Parent
  VALUE: RQ-H10SG-23
  ROLE: Refines

[DESIGN_ITEM]
UID: SW-H10SG-631
TITLE: view patient's prescription
STATEMENT: >>>
The application shall provide the ability for authorized users to view the patient's prescription information. The prescription view shall display relevant treatment prescription details associated with the patient's treatment plan.

The operator shall be able to access and review the prescription details for a patient through the patient's treatment plan view.

.. raw:: html

   <pre class="mermaid">
   sequenceDiagram
       autonumber
       
       box Application
           participant SimulationModel
           participant PrescriptionViewModel
           participant PrescriptionModel
           participant IEmrPrescriptionCommands
       end
       
       box Server
           participant PrescriptionService
       end

       Note over SimulationModel, IEmrPrescriptionCommands: User selects a site or changes its simulation
       
       SimulationModel-->>PrescriptionViewModel: simulation changed
       activate PrescriptionViewModel
       
       alt existing simulation
           PrescriptionViewModel->>PrescriptionModel: fetch prescription
           activate PrescriptionModel
           PrescriptionModel->>IEmrPrescriptionCommands: fetch simulation's prescriptions
           activate IEmrPrescriptionCommands
           
           IEmrPrescriptionCommands->>PrescriptionService: grpc:ListPrescriptionsRequest
           activate PrescriptionService
           Note over PrescriptionService: handle request
           PrescriptionService-->>IEmrPrescriptionCommands: grpc:ListPrescriptionsResponse
           deactivate PrescriptionService
           
           IEmrPrescriptionCommands-->>PrescriptionModel: list of prescriptions
           deactivate IEmrPrescriptionCommands
           
           Note over PrescriptionModel: select latest prescription
           PrescriptionModel-->>PrescriptionViewModel: [optional] prescription
           deactivate PrescriptionModel
           
           Note over PrescriptionViewModel: update prescription form
       end
       deactivate PrescriptionViewModel
   </pre>

Fulfilled requirements:
- RQ-H10SG-24-#12: Patients - Plan view - view patient's prescription
<<<
RELATIONS:
- TYPE: Parent
  VALUE: RQ-H10SG-24
  ROLE: Refines

[DESIGN_ITEM]
UID: SW-H10SG-632
TITLE: Sorting patient's list view
STATEMENT: >>>
.. raw:: html

   <pre class="mermaid">
   graph TD
       A[Plan update] --> B{Plan is approved?}
       B -- Yes --> C[Show readonly plan]
       B -- No --> D[Enable emission duration input]
       D --> E[/User selects fields/]
       E --> F{Single field selected?}
       F -- No --> G[Enable delete button]
       F -- Yes --> H{Existing plan field?}
       H -- Yes --> I[Enable update and delete buttons]
       H -- No --> J[Enable add button]
   </pre>

Note: The design specification for sorting patient's list view is not available. This appears to be a placeholder item. Refer to the requirements for SW-H10SG-632 for expected functionality.
<<<

[DESIGN_ITEM]
UID: SW-H10SG-633
TITLE: Create new patient
STATEMENT: >>>
The application shall provide functionality for authorized users to create and register new patients in the system. The patient creation process shall include:

- A patient registration form with all required fields
- Validation of mandatory fields before saving
- Data integrity checking for input data
- Patient de-duplication to prevent duplicate patient entries
- User feedback on successful registration or error conditions
- Cancel and Save buttons for form control
- Support for editing patient demographic data

Fulfilled requirements:
- RQ-H10SG-47-#7: Patients - Patient's Registration Form - Cancel Button
- RQ-H10SG-48-#8: Patients - Patient's Registration Form - Save button
- RQ-H10SG-49-#11: Patients - Patient's Registration Form - Patient Already Exist Error
- RQ-H10SG-50-#10: Patients - Patients Registration Feedback
- RQ-H10SG-51-#6: Patients - Patients Registration Form - Mandatory Fields
- RQ-H10SG-52-#13: Patients - Patients Registration Form - Input Data Integrity
- RQ-H10SG-83-#10: Patients - Edit Patient Demographic Data
- RQ-H10SG-86-#18: Patients - Patient's Registration Form - Layout
<<<
RELATIONS:
- TYPE: Parent
  VALUE: RQ-H10SG-47
  ROLE: Refines
- TYPE: Parent
  VALUE: RQ-H10SG-48
  ROLE: Refines
- TYPE: Parent
  VALUE: RQ-H10SG-49
  ROLE: Refines
- TYPE: Parent
  VALUE: RQ-H10SG-50
  ROLE: Refines
- TYPE: Parent
  VALUE: RQ-H10SG-51
  ROLE: Refines
- TYPE: Parent
  VALUE: RQ-H10SG-52
  ROLE: Refines
- TYPE: Parent
  VALUE: RQ-H10SG-83
  ROLE: Refines
- TYPE: Parent
  VALUE: RQ-H10SG-86
  ROLE: Refines

[DESIGN_ITEM]
UID: SW-H10SG-671
TITLE: Mapping Pathology Enum to UI Description
STATEMENT: >>>
The dropdown control of Field Pathology should show the following list based on the Pathology Enum IDs:

+-------------------------------+--------------------------------+--------+
| Description (UI Label)        | Name                           | number |
+===============================+================================+========+
| Infundibulo-cytic             | Infundibulo_cytic              | 1      |
+-------------------------------+--------------------------------+--------+
| Ulcerated long-standing       | Ulcerated_long_standing        | 2      |
+-------------------------------+--------------------------------+--------+
| Adenosquamous                 | Adenosquamous                  | 3      |
+-------------------------------+--------------------------------+--------+
| Desmoplastic/Metaplastic      | Desmoplastic_Metaplastic       | 4      |
+-------------------------------+--------------------------------+--------+
| Recurrent Lesion post-surgery | Recurrent_Lesion_post_surger y | 5      |
+-------------------------------+--------------------------------+--------+
| Large Lesion                  | Large_Lesion                   | 6      |
+-------------------------------+--------------------------------+--------+
| Deep Lesion                   | Deep_Lesion                    | 7      |
+-------------------------------+--------------------------------+--------+
| Rapid growth                  | Rapid_growth                   | 8      |
+-------------------------------+--------------------------------+--------+
| Extention into hair follicle  | Extention_into_hair_follicle   | 9      |
+-------------------------------+--------------------------------+--------+
<<<
RELATIONS:
- TYPE: Parent
  VALUE: RQ-H10SG-389
  ROLE: Refines

[DESIGN_ITEM]
UID: SW-H10SG-672
TITLE: Mapping Cell Type to applicable Sub cells
STATEMENT: >>>
Mapping between Pathology cell-type to applicable sub-type

+------------+---------------------------------+
| Cell Type: | Subtypes:                       |
+============+=================================+
| BCC        | Aberrant                        |
+------------+---------------------------------+
|            | Adenoid                         |
+------------+---------------------------------+
|            | Atypical Basaloid Proliferation |
+------------+---------------------------------+
<<<
RELATIONS:
- TYPE: Parent
  VALUE: RQ-H10SG-386
  ROLE: Refines

[DESIGN_ITEM]
UID: SW-H10SG-673
TITLE: Mapping Pathology type to UI
STATEMENT: >>>
The Pathology should be mapped according to the returned Enum ID:

+--------------+----------------+----------+
| DB Enum Name | DB Enum Number | UI Label |
+==============+================+==========+
| 1            | BCC            | BCC      |
+--------------+----------------+----------+
| 2            | SCC            | SCC      |
+--------------+----------------+----------+
| 3            | SCC-IS         | SCC-IS   |
+--------------+----------------+----------+
| 4            | Keloid         | Keloid   |
+--------------+----------------+----------+
| Basosquamous | 5 Basosquamous |          |
+--------------+----------------+----------+
<<<
RELATIONS:
- TYPE: Parent
  VALUE: RQ-H10SG-385
  ROLE: Refines

[DESIGN_ITEM]
UID: SW-H10SG-674
TITLE: Mapping Site Location type to UI
STATEMENT: >>>
The Site(Field) Location should be mapped according to the returned Enum ID:

+--------------+----------------+------------+
| DB Enum Name | DB Enum Number | UI Label   |
+==============+================+============+
| Breast       | 1              | Breast     |
+--------------+----------------+------------+
| LeftEar      | 2              | Ear (Left) |
+--------------+----------------+------------+

+------------------+-----+----------------------+
| RightEar         | 3   | Ear (Right)          |
+==================+=====+======================+
| Forehead         | 4   | Forehead             |
+------------------+-----+----------------------+
| Temple           | 5   | Temple               |
+------------------+-----+----------------------+
| Zygoma           | 6   | Zygoma               |
+------------------+-----+----------------------+
| PreAuricular     | 7   | Pre-Auricular        |
+------------------+-----+----------------------+
| Cheek            | 8   | Cheek                |
+------------------+-----+----------------------+
| Chin             | 9   | Chin                 |
+------------------+-----+----------------------+
| Jaw              | 10  | Jaw                  |
+------------------+-----+----------------------+
| Lip              | 11  | Lip                  |
+------------------+-----+----------------------+
| Neck             | 12  | Neck                 |
+------------------+-----+----------------------+
| Nose             | 13  | Nose                 |
+------------------+-----+----------------------+
| Scalp            | 14  | Scalp                |
+------------------+-----+----------------------+
| PostAuricular    | 15  | Post Auricular       |
+------------------+-----+----------------------+
| Trunk            | 16  | Trunk                |
+------------------+-----+----------------------+
| Chest            | 17  | Chest                |
+------------------+-----+----------------------+
| Abdomen          | 18  | Abdomen              |
+------------------+-----+----------------------+
| Back             | 19  | Back                 |
+------------------+-----+----------------------+
| LeftLowerLimb    | 20  | Lower Limb (Left)    |
+------------------+-----+----------------------+
| RightLowerLimb   | 21  | Lower Limb (Right)   |
+------------------+-----+----------------------+
| LeftUpperLimb    | 22  | Upper Limb (Left)    |
+------------------+-----+----------------------+
| RightUpperLimb   | 23  | Upper Limb (Right)   |
+------------------+-----+----------------------+
| RightUpperEyelid | 24  | Eyelid (Right Upper) |
+------------------+-----+----------------------+
| RightLowerEyelid | 25  | Eyelid (Right Lower) |
+------------------+-----+----------------------+

+-----------------+-----+---------------------+
| LeftUpperEyelid | 26  | Eyelid (Left Upper) |
+=================+=====+=====================+
| LeftLowerEyelid | 27  | Eyelid (Left Lower) |
+-----------------+-----+---------------------+
<<<
RELATIONS:
- TYPE: Parent
  VALUE: RQ-H10SG-384
  ROLE: Refines

[DESIGN_ITEM]
UID: SW-H10SG-675
TITLE: Alert for unsaved data
STATEMENT: >>>
The application shall provide an alert mechanism to notify the user when they attempt to navigate away or close the application while there are unsaved changes in the patient's treatment plan view. This alert shall inform the user of unsaved data and provide options to save or discard changes.

Fulfilled requirements:
- RQ-H10SG-382-#6: Patients - Plan View - Alert for unsaved data
<<<
RELATIONS:
- TYPE: Parent
  VALUE: RQ-H10SG-382
  ROLE: Refines

[DESIGN_ITEM]
UID: SW-H10SG-676
TITLE: Register New Collimator Flow
STATEMENT: >>>
1. First, Identify the connected collimator

2. Open the New Collimator form with the serial of the identified collimator

3. Save data to the database.
<<<
RELATIONS:
- TYPE: Parent
  VALUE: RQ-H10SG-126
  ROLE: Refines
- TYPE: Parent
  VALUE: RQ-H10SG-127
  ROLE: Refines
- TYPE: Parent
  VALUE: RQ-H10SG-383
  ROLE: Refines

[DESIGN_ITEM]
UID: SW-H10SG-680
TITLE: New Collimator Mandatory Fields
STATEMENT: >>>
The Mandatory field of a Collimator should be:

- Serial - Automatically identified from telemetry.

- Type, Energy, and SSD should be fetched/saved from the Configuration Table.

Collimator Table

+----------------------------+---------+------------+-----------------------------------------------+
| Name                       | Type    | constraint | Description                                   |
+============================+=========+============+===============================================+
| ID                         | Int64   | Not Null   | Primary key. Auto incremental                 |
+----------------------------+---------+------------+-----------------------------------------------+
| HeadID                     | Int64   | Not Null   | Foreign Key to Head table                     |
+----------------------------+---------+------------+-----------------------------------------------+
| CollimatorConfigurati onID | Int64   | Not Null   | Foreign Key to CollimatorConfigurati on table |
+----------------------------+---------+------------+-----------------------------------------------+
| CreateDate                 | Date    | Not Null   |                                               |
+----------------------------+---------+------------+-----------------------------------------------+
| Serial                     | String  | Not Null   | Unique                                        |
+----------------------------+---------+------------+-----------------------------------------------+
| IsActive                   | Tinyint | Not Null   |                                               |
+----------------------------+---------+------------+-----------------------------------------------+

CollimatorConfiguration Table

+--------------------+----------------+------------+----------------------------------------------------------------+
| Name               | Type           | constraint | Description                                                    |
+====================+================+============+================================================================+
| ID                 | Int64          |            |                                                                |
+--------------------+----------------+------------+----------------------------------------------------------------+
| CreateDate         | DateTime       | Not Null   |                                                                |
+--------------------+----------------+------------+----------------------------------------------------------------+
| Type               | TargetTypeEnum | Not Null   | Unique with Energy and SSD                                     |
+--------------------+----------------+------------+----------------------------------------------------------------+
| Energy             | Energy Enum    | Not Null   | Unique with Type and SSD                                       |
+--------------------+----------------+------------+----------------------------------------------------------------+
| SSD                | SSDType Enum   | Not Null   | Unique with Type and Energy                                    |
+--------------------+----------------+------------+----------------------------------------------------------------+
| ReferencedDoseRate | Decimal        |            | Dose rate in the a specific cell in the collimator that serves |
+--------------------+----------------+------------+----------------------------------------------------------------+


<<<
RELATIONS:
- TYPE: Parent
  VALUE: RQ-H10SG-321
  ROLE: Refines

[DESIGN_ITEM]
UID: SW-H10SG-681
TITLE: Device ID Validation Flow
STATEMENT: >>>
The Device ID is mandatory for the application to be able to run. The application should validate the existence of the DeviceID on startup.

If no Device ID is present in settings, the user asked to enter such ID in a pop-up modal. The ID is saved to settings and presisted to the database.
<<<
RELATIONS:
- TYPE: Parent
  VALUE: RQ-H10SG-249
  ROLE: Refines

[DESIGN_ITEM]
UID: SW-H10SG-682
TITLE: Emission Current Calculation
STATEMENT: >>>
The Current should be auto-calculated as the quotient of Power[W] divided by Energy Level[kV]:

Emission Current[mA] = Power[W] / Voltage[kV]

The device shall operate at a constant power of 50W.

Here are the calculated values as a dependency on Energy Level:

+----------+-------------+----------------------+
| Power[W] | Voltage[kV] | Emission Current[mA] |
+==========+=============+======================+
| 50       | 50          | 1                    |
+----------+-------------+----------------------+
| 50       | 70          | 0.71                 |
+----------+-------------+----------------------+
| 50       | 100         | 0.5                  |
+----------+-------------+----------------------+
<<<
RELATIONS:
- TYPE: Parent
  VALUE: RQ-H10SG-232
  ROLE: Refines

[DESIGN_ITEM]
UID: SW-H10SG-683
TITLE: Calculate Emission Duration
STATEMENT: >>>
The Field Actual Dose should be auto-calculate from the duration using the following function:

[Field Output factor] * [Dose Rate cGy/min] * Duration / 60

i.e. 1.05 * 320 * 18 / 60 = 100.8 cGy

Field Output factor - This value should be retrieved from the OutputFactor service.

Dose Rate - This value should be retrieved from the CollimatorConfiguration Service.

Duration - This value is calculated from the [PrescribedDose] / ([FieldOutputFactor] * [DoseRate]) * 60
<<<
RELATIONS:
- TYPE: Parent
  VALUE: RQ-H10SG-231
  ROLE: Refines

[DESIGN_ITEM]
UID: SW-H10SG-684
TITLE: Alert for an Invalid Plan when there are changes that affect its validity.
STATEMENT: >>>
The alert for an Invalid Plan will be triggered according to the following sequence diagram:

.. raw:: html

   <pre class="mermaid">
   sequenceDiagram
    actor A as Actor
    participant PrescriptionView
    participant PrescriptionViewModel

    A->>PrescriptionView: SavePrescription
    activate PrescriptionView
    
    PrescriptionView->>PrescriptionViewModel: SavePrescriptionAsync
    activate PrescriptionViewModel
    
    PrescriptionViewModel->>PrescriptionViewModel: CheckIfChangeAffectPlan
    activate PrescriptionViewModel
    deactivate PrescriptionViewModel
    
    PrescriptionViewModel->>PrescriptionViewModel: ShowMessageForUser (Plan will be delted)
    activate PrescriptionViewModel
    deactivate PrescriptionViewModel
    
    deactivate PrescriptionViewModel
    deactivate PrescriptionView
   </pre>
<<<
RELATIONS:
- TYPE: Parent
  VALUE: RQ-H10SG-162
  ROLE: Refines
- TYPE: Parent
  VALUE: RQ-H10SG-193
  ROLE: Refines

[DESIGN_ITEM]
UID: SW-H10SG-685
TITLE: Display Quality Checks Reports
STATEMENT: >>>
The quality check history shall include the following fields:
 - Timestamp
 - Performed by
 - Emission Current
 - Heater Current
 - Duration
 - Collimator configuration

The report will be retrieved from the database using the QcSampleService.
<<<
RELATIONS:
- TYPE: Parent
  VALUE: RQ-H10SG-190
  ROLE: Refines

[DESIGN_ITEM]
UID: SW-H10SG-686
TITLE: Lock application during active emission
STATEMENT: >>>
The application will be locked when a user loads a plan in the external application.
The application will use the Plan DB Event to determine when such a plan is loaded.
<<<
RELATIONS:
- TYPE: Parent
  VALUE: RQ-H10SG-187
  ROLE: Refines

[DESIGN_ITEM]
UID: SW-H10SG-687
TITLE: Load For Treatment Flow
STATEMENT: >>>
The application will be locked when a user loads a plan in the external application. 
The application shall create a Plan DB Event.
When the application receives a Plan DB Event, the internal screen shall be locked.
<<<
RELATIONS:
- TYPE: Parent
  VALUE: RQ-H10SG-184
  ROLE: Refines
- TYPE: Parent
  VALUE: RQ-H10SG-185
  ROLE: Refines

[DESIGN_ITEM]
UID: SW-H10SG-688
TITLE: Update Collimator Data Flow Diagram
STATEMENT: >>>
The application will send an update command to the Collimator Service. The following flow describes the flow:

1. User edits collimator.
2. Collimator form is opened.
3. Upon save, collimator configuration is persisted to the database using CollimatorCommands.
<<<
RELATIONS:
- TYPE: Parent
  VALUE: RQ-H10SG-128
  ROLE: Refines

[DESIGN_ITEM]
UID: SW-H10SG-689
TITLE: Create User Sequence
STATEMENT: >>>
1. The user requests to add a new user.
2. The user add form is cleared and enabled.
3. The form is validated. If validation fails, saving is disabled and the error is presented to the user.
4. The new user record is presisted to the database.
<<<
RELATIONS:
- TYPE: Parent
  VALUE: RQ-H10SG-68
  ROLE: Refines
- TYPE: Parent
  VALUE: RQ-H10SG-125
  ROLE: Refines

[DESIGN_ITEM]
UID: SW-H10SG-690
TITLE: Save Endpoint Configuration Flow Diagram
STATEMENT: >>>
The following flow describes the flow for saving Endpoint Configuration:
<<<
RELATIONS:
- TYPE: Parent
  VALUE: RQ-H10SG-124
  ROLE: Refines

[DESIGN_ITEM]
UID: SW-H10SG-691
TITLE: Import Configuration From CSV file
STATEMENT: >>>
The application will import machine configuration from CSV file. The Data imported will be validated. 
Each collimator specified in the CSV file will have its configuration loaded from the database via the CollimatorConfigurationService.
The collimator configuration will then be updated from the CSV file parameters and then persisted to the database.
<<<
RELATIONS:
- TYPE: Parent
  VALUE: RQ-H10SG-115
  ROLE: Refines
- TYPE: Parent
  VALUE: RQ-H10SG-121
  ROLE: Refines

[DESIGN_ITEM]
UID: SW-H10SG-692
TITLE: Configuring Output Factors
STATEMENT: >>>
Output Factors hould support multiple collimators.

<<<

[DESIGN_ITEM]
UID: SW-H10SG-693
TITLE: Update Output Factor Sequence
STATEMENT: >>>
The output factor of the reference field is the collimator's dose rate.
The output factor shall be persisted to the database via OutputFactorCommands.
<<<
RELATIONS:
- TYPE: Parent
  VALUE: RQ-H10SG-114
  ROLE: Refines

[DESIGN_ITEM]
UID: SW-H10SG-694
TITLE: Output Factor Configuration Flow
STATEMENT: >>>
1. The user selects a collimator configuration.
2. The application requests configuration data via the OutputFactorService.
<<<
RELATIONS:
- TYPE: Parent
  VALUE: RQ-H10SG-118
  ROLE: Refines
- TYPE: Parent
  VALUE: RQ-H10SG-119
  ROLE: Refines
- TYPE: Parent
  VALUE: RQ-H10SG-120
  ROLE: Refines

[DESIGN_ITEM]
UID: SW-H10SG-695
TITLE: Heater Current Configuration Sequence
STATEMENT: >>>
The application shall store the heater current in the database. When the user changes the heater current, it shall be validated before saving. Validation errors shall be presented to the user.

When retrieving the current configuration, if no such configuration exists, a configuration record shall be created.
<<<
RELATIONS:
- TYPE: Parent
  VALUE: RQ-H10SG-112
  ROLE: Refines

[DESIGN_ITEM]
UID: SW-H10SG-696
TITLE: Configure Correction Matrix for Magnetometer
STATEMENT: >>>
.. raw:: html

   <pre class="mermaid">
   sequenceDiagram
    box rgb(245, 245, 245) Application
        participant ConfigurationViewModel
        participant MagnetometerViewMode
        participant MagnetometerCorrections
        participant IReferenceFieldCommands
        participant ICorrectionMatrixCommands
    end
    
    box rgb(245, 245, 245) Server
        participant ReferenceFieldService
        participant CorrectionMatrixService
    end

    Note over ConfigurationViewModel: User selects a collimator configuration
    
    activate ConfigurationViewModel
    ConfigurationViewModel->>MagnetometerCorrections: fetch configuration data
    activate MagnetometerCorrections
    
    MagnetometerCorrections->>IReferenceFieldCommands: read reference fields by preset id
    activate IReferenceFieldCommands
    
    IReferenceFieldCommands->>ReferenceFieldService: grpc:ListReferneceFieldsRequest
    activate ReferenceFieldService
    
    ReferenceFieldService->>ReferenceFieldService: handle request
    ReferenceFieldService-->>IReferenceFieldCommands: grpc:ListReferneceFieldsResponse
    deactivate ReferenceFieldService
    
    IReferenceFieldCommands-->>MagnetometerCorrections: list of reference field records
    deactivate IReferenceFieldCommands
    
    MagnetometerCorrections->>ICorrectionMatrixCommands: read correction matrices by preset id
    activate ICorrectionMatrixCommands
    
    ICorrectionMatrixCommands->>CorrectionMatrixService: grpc:ListCorrectionMatricesRequest
    activate CorrectionMatrixService
    
    CorrectionMatrixService->>CorrectionMatrixService: handle request
    CorrectionMatrixService-->>ICorrectionMatrixCommands: grpc:ListCorrectionMatricesResponse
    deactivate CorrectionMatrixService
    
    ICorrectionMatrixCommands-->>MagnetometerCorrections: list of correction matrix records
    deactivate ICorrectionMatrixCommands
    
    MagnetometerCorrections->>MagnetometerCorrections: update configuration
    
    MagnetometerCorrections-->>MagnetometerViewMode: configuration changed
    deactivate MagnetometerCorrections
    deactivate ConfigurationViewModel
   </pre>
<<<
RELATIONS:
- TYPE: Parent
  VALUE: RQ-H10SG-111
  ROLE: Refines

[DESIGN_ITEM]
UID: SW-H10SG-698
TITLE: Retrieve Treatment History Sequence
STATEMENT: >>>
TBD
<<<
RELATIONS:
- TYPE: Parent
  VALUE: RQ-H10SG-94
  ROLE: Refines

[DESIGN_ITEM]
UID: SW-H10SG-699
TITLE: Retrieve Actual Treatment Fields
STATEMENT: >>>
TBD
<<<
RELATIONS:
- TYPE: Parent
  VALUE: RQ-H10SG-95
  ROLE: Refines

[DESIGN_ITEM]
UID: SW-H10SG-700
TITLE: Create Patient's Treatment Simulation
STATEMENT: >>>
1. The user requests to add a simulation.
2. The simulation form is cleared and enabled.
3. The form is validated. If there is a validation error, the form is disabled and the user is presented the error.
4. The simulation and site simulation records are persisted to the database.
<<<
RELATIONS:
- TYPE: Parent
  VALUE: RQ-H10SG-89
  ROLE: Refines

[DESIGN_ITEM]
UID: SW-H10SG-701
TITLE: Retrieve Patient's Treatment Simulation
STATEMENT: >>>
TBD
<<<
RELATIONS:
- TYPE: Parent
  VALUE: RQ-H10SG-88
  ROLE: Refines

[DESIGN_ITEM]
UID: SW-H10SG-702
TITLE: Create Patient's Prescription Sequence
STATEMENT: >>>
1. When the user adds a prescription, the prescription form is cleared and enabled.
2. Entered prescription data is validated. If validation fails, saving is disabled and the user is presented the error.
3. The prescription and the simulation's prescription records are saved in the database.
<<<
RELATIONS:
- TYPE: Parent
  VALUE: RQ-H10SG-80
  ROLE: Refines

[DESIGN_ITEM]
UID: SW-H10SG-703
TITLE: Actual Treatment Delivered
STATEMENT: >>>
.. raw:: html

   <pre class="mermaid">
   sequenceDiagram
    box rgb(245, 245, 245) Application
        participant TreatmentViewModel
        participant TreatmentHistoryModel
        participant IEmrTreatmentCommands
        participant IEmrActualTreatmentFieldCommands
    end
    
    box rgb(245, 245, 245) Server
        participant TreatmentService
        participant TreatmentFieldService
    end

    Note over TreatmentViewModel,IEmrActualTreatmentFieldCommands: current plan changed or current treatment process finished
    
    TreatmentViewModel-->>TreatmentHistoryModel: fetch/update treatment data
    activate TreatmentHistoryModel
    
    TreatmentHistoryModel->>IEmrTreatmentCommands: fetch plan treatments
    activate IEmrTreatmentCommands
    
    IEmrTreatmentCommands->>TreatmentService: grpc: ListTreatmentsRequest
    activate TreatmentService
    
    TreatmentService->>TreatmentService: handle request
    TreatmentService-->>IEmrTreatmentCommands: grpc: ListTreatmentsResponse
    deactivate TreatmentService
    
    IEmrTreatmentCommands-->>TreatmentHistoryModel: list of treatments
    deactivate IEmrTreatmentCommands
    
    loop [for each treatment record]
        TreatmentHistoryModel->>IEmrActualTreatmentFieldCommands: fetch treatment fields
        activate IEmrActualTreatmentFieldCommands
        
        IEmrActualTreatmentFieldCommands->>TreatmentFieldService: grpc:ListActualTreatmentFieldsRequest
        activate TreatmentFieldService
        
        TreatmentFieldService->>TreatmentFieldService: handle request
        TreatmentFieldService-->>IEmrActualTreatmentFieldCommands: grpc:ListActualTreatmentFieldsResponse
        deactivate TreatmentFieldService
        
        IEmrActualTreatmentFieldCommands-->>TreatmentHistoryModel: list of actual fields
        deactivate IEmrActualTreatmentFieldCommands
        
        TreatmentHistoryModel->>TreatmentHistoryModel: sort fields and set to treatment
        TreatmentHistoryModel->>TreatmentHistoryModel: build treatment summary
        
        TreatmentHistoryModel-->>TreatmentViewModel: 
    end
    deactivate TreatmentHistoryModel
   </pre>
<<<

[DESIGN_ITEM]
UID: SW-H10SG-705
TITLE: Save log records sequence
STATEMENT: >>>
TBD
<<<
RELATIONS:
- TYPE: Parent
  VALUE: RQ-H10SG-45
  ROLE: Refines
- TYPE: Parent
  VALUE: RQ-H10SG-67
  ROLE: Refines

[DESIGN_ITEM]
UID: SW-H10SG-708
TITLE: Display System Telemetry
STATEMENT: >>>
The application should subscribe to a UDP event from the firmware to get the system telemetry.
<<<
RELATIONS:
- TYPE: Parent
  VALUE: RQ-H10SG-54
  ROLE: Refines

[DESIGN_ITEM]
UID: SW-H10SG-709
TITLE: Cancel Load For Treatment Flow
STATEMENT: >>>
The application is unlocked when a user cancels.
<<<
RELATIONS:
- TYPE: Parent
  VALUE: RQ-H10SG-186
  ROLE: Refines

[DESIGN_ITEM]
UID: SW-H10SG-710
TITLE: Show message for DB communication error
STATEMENT: >>>
The application will show a DB Communication error when the gRPC command throws a timeout exception. The exception will be populated through the MVVM model.
<<<

[DESIGN_ITEM]
UID: SW-H10SG-711
TITLE: Retrieve Patients List
STATEMENT: >>>
The flow for retrieving the patient list should be implemented as described in the following sequence diagram:
<<<
RELATIONS:
- TYPE: Parent
  VALUE: RQ-H10SG-40
  ROLE: Refines
- TYPE: Parent
  VALUE: RQ-H10SG-50
  ROLE: Refines

[DESIGN_ITEM]
UID: SW-H10SG-712
TITLE: Retrieve Patient's Fields (Sites)
STATEMENT: >>>
The flow for retrieving Patient's Fields ( Sites) should be implemented as described in the following sequence diagram:
<<<
RELATIONS:
- TYPE: Parent
  VALUE: RQ-H10SG-388
  ROLE: Refines

[DESIGN_ITEM]
UID: SW-H10SG-713
TITLE: Retrieve System Signals
STATEMENT: >>>
The flow for retrieving System Signals should be implemented as described in the following sequence diagram:
<<<
RELATIONS:
- TYPE: Parent
  VALUE: RQ-H10SG-65
  ROLE: Refines

[[/SECTION]]
